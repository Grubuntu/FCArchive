# FCArchive for FreeCAD
#
# Macro for archiving FCStd files in 7z format to save disk space.
# The basic FreeCAD file format is ZIP compression, which is not 
# optimal in terms of compression ratio. Using the 7z compression
# format saves up to 75% space without any loss of data.
#
# This macro is for demonstration purposes only and is not 
# guaranteed to work.This macro uses the py7zr library 
# https://github.com/miurahr/py7zr LGPL-2.1 license
#
# Copyright (C) 2025 Grubuntu
#
# This library is free software; you can redistribute it and/or
# modify it under the terms of the GNU Lesser General Public
# License as published by the Free Software Foundation; either
# version 2.1 of the License, or (at your option) any later version.
#
# This library is distributed in the hope that it will be useful,
# but WITHOUT ANY WARRANTY; without even the implied warranty of
# MERCHANTABILITY or FITNESS FOR A PARTICULAR PURPOSE.  See the GNU
# Lesser General Public License for more details.
#
# You should have received a copy of the GNU Lesser General Public
# License along with this library; if not, write to the Free Software
# Foundation, Inc., 51 Franklin Street, Fifth Floor, Boston, MA  02110-1301 USA
#
# FCArchive V1.0

import os
import subprocess
import sys
import zipfile
import tempfile
import shutil

try:
    import py7zr
except ImportError:
    py7zr = None

from pathlib import Path
from PySide6 import QtCore
from PySide6.QtWidgets import (
    QWidget, QPushButton, QVBoxLayout, QFileDialog,
    QTextEdit, QLabel, QMessageBox, QProgressBar
)
from freecad import project_utility
from freecad.utils import get_python_exe
import addonmanager_utilities as utils
import FreeCAD

# check if library py7zr is present
def check_py7zr():
    try:
        import py7zr
        # FreeCAD.Console.PrintError("✅ Py7zr is already installed.\n")
        return py7zr
    except ImportError:
        FreeCAD.Console.PrintError("❌ Missing Py7zr dependency.\n")
        pass  # On continue pour demander à l'utilisateur

    # ask user for installation
    reponse = QMessageBox.question(
        None,
        "Installation required."
        "The 'py7zr' module is necessary to compress/decompress files. Would you like to continue the installation?",
        QMessageBox.Yes | QMessageBox.No
    )

    if reponse != QMessageBox.Yes:
        FreeCAD.Console.PrintError("❌ Installation canceled by the user.\n")
        return None

    fc_dir = FreeCAD.getHomePath()
    pkg_name = "py7zr"

    # check platform (Windows or Linux/MacOs)
    if sys.platform.startswith("win"):
        python_exe = os.path.join(fc_dir, "bin", "python.exe")
        packages_dir = os.path.join(fc_dir, "lib")

        # check if pip is present
        try:
            subprocess.check_call([python_exe, "-m", "pip", "--version"], stdout=subprocess.DEVNULL, stderr=subprocess.DEVNULL)
        except subprocess.CalledProcessError:
            FreeCAD.Console.PrintError("❌ pip is not available. Unable to install py7zr automatically.\n Please install pip manually.")
            return None

        # try to install py7zr
        try:
            subprocess.check_call([python_exe, "-m", "pip", "install","--disable-pip-version-check", "--target", packages_dir, pkg_name])
            # subprocess.check_call([python_exe, "-m", "pip", "uninstall", pkg_name])

            FreeCAD.Console.PrintError("✅ The installation of py7zr was successful.\n")
        except subprocess.CalledProcessError:
            FreeCAD.Console.PrintError("❌ The installation of py7zr has failed.\n")
            return None

    else:  # Linux ou macOS
        python_exe = get_python_exe()
        vendor_path = utils.get_pip_target_directory()
        packages_dir = vendor_path

        if not os.path.exists(vendor_path):
            os.makedirs(vendor_path)

        # try to install py7zr
        try:
            subprocess.check_call([
                python_exe, "-m", "pip", "install", "--disable-pip-version-check",
                "--target", vendor_path, pkg_name
            ])
            FreeCAD.Console.PrintError("✅ The installation of py7zr was successful.\n")
        except Exception as e:
            FreeCAD.Console.PrintError(f"❌ The installation of py7zr has failed:{e}\n")
            return None

    if packages_dir not in sys.path:
        sys.path.insert(0, packages_dir)

    # test py7zr installation
    try:
        import py7zr
        return py7zr
    except ImportError:
        FreeCAD.Console.PrintError("❌ Py7zr is still missing after installation.\n")
        return None


class WorkerSignals(QtCore.QObject):
    progress = QtCore.Signal(int)
    log = QtCore.Signal(str)
    finished = QtCore.Signal()
    success = QtCore.Signal(bool)


class CompressorWorker(QtCore.QRunnable):
    def __init__(self, fcstd_path, fichier_destination):
        super().__init__()
        self.fcstd_path = fcstd_path
        self.fichier_destination = fichier_destination
        self.signals = WorkerSignals()

    @QtCore.Slot()
    def run(self):
        if not py7zr:
            self.signals.log.emit("❌ The Py7zr module is not found.")
            self.signals.success.emit(False)
            self.signals.finished.emit()
            return
            
        temp_dir = tempfile.mkdtemp()
        try:
            # Décompression du fichier FCStd
            with zipfile.ZipFile(self.fcstd_path, 'r') as zip_ref:
                zip_ref.extractall(temp_dir)
                
            taille_originale = os.path.getsize(self.fcstd_path) / (1024 * 1024)
            self.signals.log.emit(f"📋 Original file size.:{taille_originale:.2f} Mo")
            self.signals.log.emit("✅ Compressing...")

            # Compression en 7z
            with py7zr.SevenZipFile(self.fichier_destination, mode='w') as archive:
                files = [
                    os.path.join(root, f)
                    for root, _, fs in os.walk(temp_dir)
                    for f in fs
                ]
                total = len(files)
                for i, full_path in enumerate(files, 1):
                    rel_path = os.path.relpath(full_path, temp_dir)
                    archive.write(full_path, arcname=rel_path)
                    self.signals.progress.emit(int(i / total * 100))
                    # QtCore.QThread.msleep(0.1)

            taille_7z = os.path.getsize(self.fichier_destination) / (1024 * 1024)
            
            taux = 100 * (1 - taille_7z / taille_originale)
            self.signals.log.emit("✅ Compression successful!")
            self.signals.log.emit(f"📦 Archive size: {taille_7z:.2f} Mo")
            self.signals.log.emit(f"📉 Compression rate: {taux:.1f} %")

            self.signals.success.emit(True)

        except Exception as e:
            self.signals.log.emit(f"❌ Error : {e}")
            self.signals.success.emit(False)
        finally:
            shutil.rmtree(temp_dir)
            self.signals.finished.emit()


class DesarchiverWorker(QtCore.QRunnable):
    def __init__(self, archive_7z, fichier_sortie_fcstd, progress_bar, btn_ouvrir_fichier):
        super().__init__()
        self.archive_7z = archive_7z
        self.fichier_sortie_fcstd = fichier_sortie_fcstd
        self.signals = WorkerSignals()
        self.progress_bar = progress_bar
        self.btn_ouvrir_fichier = btn_ouvrir_fichier

    @QtCore.Slot()
    def run(self):
        if not py7zr:
            self.signals.log.emit("❌ The Py7zr module is not found.")
            self.signals.success.emit(False)
            self.signals.finished.emit()
            return
        temp_dir = tempfile.mkdtemp()

        # uncompress
        try:
            self.signals.log.emit(f"⏳ Decompression of {self.archive_7z}...")
            with py7zr.SevenZipFile(self.archive_7z, mode='r') as archive:
                archive.extractall(path=temp_dir)
                self.progress_bar.setValue(70)
        except Exception as e:
            self.signals.log.emit(f"❌ Error during decompression:{e}")
            self.signals.success.emit(False)
            shutil.rmtree(temp_dir)
            self.signals.finished.emit()
            return

        document_xml = os.path.join(temp_dir, "Document.xml")
        if not os.path.exists(document_xml):
            self.signals.log.emit("❌ Document.xml not found. Invalid archive?")
            self.signals.success.emit(False)
            shutil.rmtree(temp_dir)
            self.signals.finished.emit()
            return

        try:
            project_utility.createDocument(document_xml, self.fichier_sortie_fcstd)
            taille_fcstd = os.path.getsize(self.fichier_sortie_fcstd) / (1024 * 1024)
            self.signals.log.emit(f"✅ Document rebuilt successfully:{self.fichier_sortie_fcstd} ({taille_fcstd:.2f} Mo)")
            self.progress_bar.setValue(100)
            self.signals.success.emit(True)

        except Exception as e:
            self.signals.log.emit(f"❌ Error while creating the document:{e}")
            self.signals.success.emit(False)
        finally:
            try:
                shutil.rmtree(temp_dir)
            except Exception as e:
                self.signals.log.emit(f"⚠️ Unable to delete the temporary folder:{e}")
            self.signals.finished.emit()


class FCStdCompressor(QWidget):
    def __init__(self):
        super().__init__()
        self.setWindowTitle("Archiving FreeCAD file")
        self.setMinimumWidth(400)
        self.setWindowModality(QtCore.Qt.ApplicationModal)
        self.move(QtCore.QCoreApplication.instance().activeWindow().geometry().center() - self.rect().center())

        self.label = QLabel("FreeCAD file archiving management (.FCStd)")
        self.btn_compresser_fcstd = QPushButton("🗃️ Archiving a file .FCStd")
        self.btn_extraire = QPushButton("🗂 Extracting an archive .FCArchive")
        self.btn_ouvrir_fichier = QPushButton("📂 Opening the extracted file .FCStd")
        self.btn_ouvrir_fichier.setEnabled(False)
        self.btn_quitter = QPushButton("❌ Quit")
        self.progress_bar = QProgressBar()
        self.log = QTextEdit()
        self.log.setReadOnly(True)

        layout = QVBoxLayout(self)
        layout.setSpacing(10)
        layout.setContentsMargins(10, 10, 10, 10)
        
        for widget in [self.label, self.btn_compresser_fcstd, self.btn_extraire, self.btn_ouvrir_fichier, self.progress_bar, self.log, self.btn_quitter]:
            layout.addWidget(widget)

        self.btn_compresser_fcstd.clicked.connect(self.action_compresser_fcstd)
        self.btn_extraire.clicked.connect(self.action_desarchiver)
        self.btn_ouvrir_fichier.clicked.connect(self.ouvrir_fcstd)
        self.btn_quitter.clicked.connect(self.close)

        self.threadpool = QtCore.QThreadPool()


    def log_append(self, text):
        self.log.append(text)
        self.log.ensureCursorVisible()

    def set_buttons_enabled(self, enabled):
        self.btn_compresser_fcstd.setEnabled(enabled)
        self.btn_extraire.setEnabled(enabled)

    def action_compresser_fcstd(self):
        fcstd_path, _ = QFileDialog.getOpenFileName(self, "Choose a file .FCStd", "", "FCStd File (*.FCStd)")
        if not fcstd_path or not os.path.isfile(fcstd_path):
            QMessageBox.warning(self, "Error", "FCStd File invalid.")
            return

        fichier_destination, _ = QFileDialog.getSaveFileName(
            self, "Save as...", fcstd_path.replace(".FCStd", ".FCArchive"), "Archive FreeCAD (*.FCArchive)"
        )
        if not fichier_destination:
            return
            
        if fcstd_path in [doc.FileName for doc in FreeCAD.listDocuments().values()]:
            QMessageBox.warning(self, "Error", "This file is currently open in FreeCAD. Close it first.")
            return

        self.set_buttons_enabled(False)
        self.progress_bar.setValue(0)

        workerComp = CompressorWorker(fcstd_path, fichier_destination)
        workerComp.signals.progress.connect(self.progress_bar.setValue)
        workerComp.signals.log.connect(self.log_append)
        workerComp.signals.finished.connect(lambda: self.set_buttons_enabled(True))
        workerComp.signals.success.connect(lambda ok: self.btn_ouvrir_fichier.setEnabled(False))

        self.threadpool.start(workerComp)

    def action_desarchiver(self):
        # self.btn_ouvrir_fichier.setEnabled(False)
        archive_7z, _ = QFileDialog.getOpenFileName(self, "Choose an archive", "", "FreeCAD Archive (*.FCArchive)")
        if not archive_7z:
            return

        fichier_sortie_fcstd, _ = QFileDialog.getSaveFileName(
            self, "Save as...", archive_7z.replace(".FCArchive", ".FCStd"), "FCStd File (*.FCStd)"
        )
        if not fichier_sortie_fcstd:
            return

        self.fichier_sortie_fcstd = fichier_sortie_fcstd
        self.progress_bar.setValue(35)

        worker = DesarchiverWorker(archive_7z, fichier_sortie_fcstd, self.progress_bar, self.btn_ouvrir_fichier)
        worker.signals.log.connect(self.log_append)
        worker.signals.progress.connect(self.progress_bar.setValue)
        worker.signals.finished.connect(lambda: self.set_buttons_enabled(True))
        worker.signals.finished.connect(lambda: self.progress_bar.setValue(100))
        worker.signals.success.connect(lambda ok: self.btn_ouvrir_fichier.setEnabled(True))
        worker.signals.success.connect(lambda ok: self.btn_ouvrir_fichier.setText(f"📂 Open {os.path.basename(fichier_sortie_fcstd)} in FreeCAD") if ok else None)

        self.threadpool.start(worker)

    def ouvrir_fcstd(self):
        fichier = self.fichier_sortie_fcstd
        try:
            self.log_append("✅ Opening the file...")
            FreeCAD.openDocument(fichier)
        except Exception as e:
            self.log_append(f"❌ Error while opening the file:{e}")

# Affichage dans FreeCAD
if 'myWin' in globals():
    try:
        myWin.close()
    except:
        pass
    
py7zr = check_py7zr()
if py7zr :
    myWin = FCStdCompressor()
    myWin.show()
else:
    FreeCAD.Console.PrintError("❌ Py7zr: Missing dependency. Operation aborted.\n")
